from CfdOF import CfdTools
from CfdOF.Solve import CfdSolidMaterial

aluminium = {
    "Author": "AluminiumSolid", "AuthorAndLicense": "",
    "CardName": "AluminiumSolid", "Density": "2699 kg/m^3",
    "Description": "Aluminium solid thermal properties for CHT simulation",
    "License": "", "Name": "Aluminium_solid", "ReferenceSource": "",
    "SourceURL": "", "SpecificHeat": "897 J/kg/K",
    "ThermalConductivity": "237 W/m/K", "Type": "Solid",
}

def add_solid(name, label, shape, material, heat_generation="0 W/m^3"):
    solid = CfdSolidMaterial.makeCfdSolidMaterial(name)
    CfdTools.getActiveAnalysis().addObject(solid)
    solid.Label = label
    solid.Material = material
    solid.HeatGeneration = heat_generation
    solid.ShapeRefs = [(shape, ("Solid1",))]
    return solid

add_solid("SolidProperties", "heat_sink_volume001",
          App.ActiveDocument.Fusion, aluminium)
add_solid("SolidProperties", "PCB_volume001", App.ActiveDocument.Box001, {
    "Density": "1.1e-06 kg/mm^3", "Description": "User-entered properties",
    "Name": "Custom", "SpecificHeat": "200000000.0 mm^2/(s^2*K)",
    "ThermalConductivity": "200.0 mm*kg/(s^3*K)", "Type": "Solid",
})
add_solid("SolidProperties", "hot_microchip_volume001",
          App.ActiveDocument.Box002, aluminium, "1e+09 W/m^3")
add_solid("SolidProperties", "Polypropylene_solid001", App.ActiveDocument.Body, {
    "Author": "PolypropyleneSolid", "AuthorAndLicense": "",
    "CardName": "PolypropyleneSolid", "Density": "918 kg/m^3",
    "Description": "Polypropylene solid thermal properties", "License": "",
    "Name": "Polypropylene_solid",
    "ReferenceSource": "https://www.matweb.com/search/DataSheet.aspx?MatGUID=a882a1c603374e278d062f106dfda95b",
    "SourceURL": "", "SpecificHeat": "1920 J/kg/K",
    "ThermalConductivity": "0.249 W/m/K", "Type": "Solid",
})
App.ActiveDocument.recompute()
