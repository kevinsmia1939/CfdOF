from CfdOF import CfdTools
from CfdOF.Solve import CfdMeanVelocityForce

force = CfdMeanVelocityForce.makeCfdMeanVelocityForce()
CfdTools.getActiveAnalysis().addObject(force)
force.Label = "MeanVelocityForce001"
force.SelectionMode = "cellZone"
force.CellZoneShapeNames = ["Cylinder"]
force.CellZoneCylinderSpecs = ["Cylinder,13,8,150,150,26"]
force.Direction = App.Vector(0, 0, 1)
force.Ubar = App.Vector(0, 0, 0.2)
force.Relaxation = 0.05
App.ActiveDocument.recompute()
