import FreeCAD as App
import Part
import BOPTools.SplitFeatures as SplitFeatures


document_name = "microchip_cooling_ncc"

if document_name in App.listDocuments():
    App.closeDocument(document_name)
doc = App.newDocument(document_name)
App.setActiveDocument(doc.Name)


def make_box(name, label, length, width, height, placement):
    obj = doc.addObject("Part::Box", name)
    obj.Label = label
    obj.Length = "{} mm".format(length)
    obj.Width = "{} mm".format(width)
    obj.Height = "{} mm".format(height)
    obj.Placement.Base = App.Vector(*placement)
    return obj


Box = make_box("Box", "room", 120, 120, 100, (89, 90, 0))
Box001 = make_box("Box001", "PCB", 100, 100, 1, (100, 100, 10))
Box002 = make_box("Box002", "microchip", 30, 30, 1, (135, 135, 11))

# Heat sink: 30 x 30 x 3 mm base plus seven 1 mm thick fins, then placed on
# top of the microchip. Keep object names aligned with the original demo.
Box003 = make_box("Box003", "Cube", 30, 30, 3, (0, 0, 0))
fin_pitch = 29.0 / 6.0
Fins = [
    make_box("Box{:03d}".format(4 + i), "Cube{:03d}".format(i + 1), 30, 1, 12, (0, fin_pitch * i, 0))
    for i in range(7)
]

Fusion = doc.addObject("Part::MultiFuse", "Fusion")
Fusion.Label = "heat_sink"
Fusion.Shapes = [Box003] + Fins
Fusion.Placement.Base = App.Vector(135, 135, 12)

# Fan case: square 30 x 30 x 10 mm duct with a 28 mm diameter cylindrical hole.
outer = Part.makeBox(30, 30, 10, App.Vector(-15, -15, 0))
inner = Part.makeCylinder(14, 10, App.Vector(0, 0, 0))
Body = doc.addObject("Part::Feature", "Body")
Body.Label = "fan case"
Body.Shape = outer.cut(inner)
Body.Placement.Base = App.Vector(150, 150, 24)

Cylinder = doc.addObject("Part::Cylinder", "Cylinder")
Cylinder.Label = "fan"
Cylinder.Radius = "13 mm"
Cylinder.Height = "8 mm"
Cylinder.Placement.Base = App.Vector(150, 150, 26)

doc.recompute()

BooleanFragments = SplitFeatures.makeBooleanFragments(name="BooleanFragments")
BooleanFragments.Label = "BooleanFragments"
BooleanFragments.Objects = [Fusion, Box002, Box001, Box, Body]
BooleanFragments.Mode = "Standard"
doc.recompute()


def add_region_object(name, label, solid):
    obj = doc.addObject("Part::Feature", name)
    obj.Label = label
    obj.Shape = solid
    return obj


def close_to(value, target, tol=1e-6):
    return abs(value - target) <= tol


def find_solid(predicate, description):
    matches = [solid for solid in BooleanFragments.Shape.Solids if predicate(solid.BoundBox)]
    if len(matches) != 1:
        raise RuntimeError("Expected one {} solid, found {}".format(description, len(matches)))
    return matches[0]


FluidRegion = add_region_object(
    "FluidRegion",
    "fluid_volume001",
    max(BooleanFragments.Shape.Solids, key=lambda solid: solid.Volume),
)
PCBRegion = add_region_object(
    "PCBRegion",
    "PCB_volume001",
    find_solid(
        lambda bb: close_to(bb.XMin, 100) and close_to(bb.XMax, 200)
        and close_to(bb.YMin, 100) and close_to(bb.YMax, 200)
        and close_to(bb.ZMin, 10) and close_to(bb.ZMax, 11),
        "PCB",
    ),
)
MicrochipRegion = add_region_object(
    "MicrochipRegion",
    "hot_microchip_volume001",
    find_solid(
        lambda bb: close_to(bb.XMin, 135) and close_to(bb.XMax, 165)
        and close_to(bb.YMin, 135) and close_to(bb.YMax, 165)
        and close_to(bb.ZMin, 11) and close_to(bb.ZMax, 12),
        "microchip",
    ),
)
HeatSinkRegion = add_region_object(
    "HeatSinkRegion",
    "heat_sink_volume001",
    find_solid(
        lambda bb: close_to(bb.XMin, 135) and close_to(bb.XMax, 165)
        and close_to(bb.YMin, 135) and close_to(bb.YMax, 165)
        and close_to(bb.ZMin, 12) and close_to(bb.ZMax, 24),
        "heat sink",
    ),
)
FanCaseRegion = add_region_object(
    "FanCaseRegion",
    "Polypropylene_solid001",
    find_solid(
        lambda bb: close_to(bb.XMin, 135) and close_to(bb.XMax, 165)
        and close_to(bb.YMin, 135) and close_to(bb.YMax, 165)
        and close_to(bb.ZMin, 24) and close_to(bb.ZMax, 34),
        "fan case",
    ),
)

for obj in [Box, Box001, Box002, Box003] + Fins + [Fusion, Body, BooleanFragments]:
    if obj.ViewObject:
        obj.ViewObject.Visibility = False

doc.recompute()
