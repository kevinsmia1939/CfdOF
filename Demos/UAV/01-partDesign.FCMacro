import Part
import os
from freecad import module_io
module_io.OpenInsertObject("ImportGui", os.path.join(os.path.dirname(__file__), "UAV.IGS"), "open")
Gui.SendMsgToActiveView("ViewFit")
FreeCAD.ActiveDocument.recompute()
App.ActiveDocument.removeObject("Part__Feature001")
App.ActiveDocument.removeObject("Part__Feature006")
App.ActiveDocument.removeObject("Part__Feature005")
App.ActiveDocument.removeObject("Part__Feature003")
App.ActiveDocument.removeObject("Part__Feature004")
App.ActiveDocument.removeObject("Part__Feature")
App.ActiveDocument.removeObject("Part__Feature019")
App.ActiveDocument.removeObject("Part__Feature022")
App.ActiveDocument.removeObject("Part__Feature017")
App.ActiveDocument.removeObject("Part__Feature021")
App.ActiveDocument.removeObject("Part__Feature020")
App.ActiveDocument.removeObject("Part__Feature016")
App.ActiveDocument.removeObject("Part__Feature014")
App.ActiveDocument.removeObject("Part__Feature011")
App.ActiveDocument.removeObject("Part__Feature012")
App.ActiveDocument.removeObject("Part__Feature008")
App.ActiveDocument.removeObject("Part__Feature009")
App.ActiveDocument.removeObject("Part__Feature013")
App.ActiveDocument.removeObject("Part__Feature018")
App.ActiveDocument.removeObject("Part__Feature023")
App.ActiveDocument.removeObject("Part__Feature002")
App.ActiveDocument.removeObject("Part__Feature007")
App.ActiveDocument.removeObject("Part__Feature010")
App.ActiveDocument.removeObject("Part__Feature015")
App.ActiveDocument.recompute()

Gui.activateWorkbench("DraftWorkbench")
import Draft
Draft.upgrade(App.ActiveDocument.RootObjects,delete=True)
FreeCAD.ActiveDocument.recompute()

Gui.activateWorkbench("PartWorkbench")

App.ActiveDocument.addObject("Part::Box","Box001")
App.ActiveDocument.ActiveObject.Label = "Cube001"
App.ActiveDocument.getObject("Box001").Length = '2500 mm'
App.ActiveDocument.getObject("Box001").Width = '4000 mm'
App.ActiveDocument.getObject("Box001").Height = '6000 mm'
App.ActiveDocument.getObject("Box001").Placement = App.Placement(App.Vector(0,-2000,-3500),App.Rotation(App.Vector(0,0,1),0))
App.ActiveDocument.recompute()
Gui.SendMsgToActiveView("ViewFit")

App.activeDocument().addObject("Part::Compound","Compound001")
App.activeDocument().Compound001.Links = [App.activeDocument().Box001,App.activeDocument().Compound]
App.ActiveDocument.recompute()
Gui.SendMsgToActiveView("ViewFit")

Gui.ActiveDocument.getObject('Compound').Transparency = 50
